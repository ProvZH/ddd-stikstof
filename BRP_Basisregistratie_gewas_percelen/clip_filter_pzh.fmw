FME workspace clip_filter_pzh.fmw
Title: ClipProvincie

Parameters:
- DestDataset_GEOPACKAGE = BRP_2018_Clip_pzh   # GeoPackage File
- Provincie = Zuid-Holland
- SourceDataset_FILEGDB = http://geodata.nationaalgeoregister.nl/brpgewaspercelen/extract/2018-definitief/brpgewaspercelen.zip   # File Geodatabase
- SourceDataset_WFS = https://geodata.nationaalgeoregister.nl/bestuurlijkegrenzen/wfs?   # Source WFS (Web Feature Service) URL

Readers:
- WFS_1: WFS from $(SourceDataset_WFS) in EPSG:28992
- FILEGDB_1: FILEGDB from $(SourceDataset_FILEGDB)

Writers:
- GEOPACKAGE_1: GEOPACKAGE to $(DestDataset_GEOPACKAGE)

Note: BRP 2018
BRP_gewaspercelen_2018 (reader FILEGDB_1)
    attributes: OBJECTID objectid, CAT_GEWASCATEGORIE text(60), GWS_GEWASCODE text(10), GEOMETRIE_Length double, GEOMETRIE_Area double, GWS_GEWAS text(255)
    -> Clipper [CLIPPEE]
    -> SpatialFilter [Candidate]
Note: Bestuurlijke grens Zuid-Holland
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> Clipper [CLIPPER]
    -> SpatialFilter [Filter]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> BRP_2018_clip (writer GEOPACKAGE_1)
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> BRP_2018_filter (writer GEOPACKAGE_1)
Note: Filter (selection)
BRP_2018_filter (writer GEOPACKAGE_1) [off]
    attributes: OBJECTID mediumint, BOFEK2012 smallint, PAWN smallint, Shape_Length double, Shape_Area double

Bookmark: Writer Feature Types
Note: Clip (cookie cutter)
BRP_2018_clip (writer GEOPACKAGE_1)
    attributes: OBJECTID mediumint, BOFEK2012 smallint, PAWN smallint, Shape_Length double, Shape_Area double
